ZXCESPERFORMANCE-MIB DEFINITIONS ::= BEGIN

IMPORTS
        Unsigned32, MODULE-IDENTITY, OBJECT-TYPE
                                         FROM SNMPv2-SMI
        zxAnCesMib                       FROM ZTE-MASTER-MIB
        zxSonetIfIndex, zxSonetVTIfIndex FROM ZXSONETIF-MIB
        zxCesCardIndex                   FROM ZXCESCARDPROP-MIB
        zxPwIndex                        FROM ZXPW-STD-MIB;

zxAnCesPm        MODULE-IDENTITY
    LAST-UPDATED "200704040000Z"
    ORGANIZATION    "Zhongxing Telcom Co. Ltd."
    CONTACT-INFO    "Zhongxing Telcom Co. Ltd.
                     E-mail: info@mail.zte.com.cn
                     http  : www.zte.com.cn or www.zhongxing.com"

    DESCRIPTION
         ""
    ::= { zxAnCesMib 6 }

    zxAnCesPmInfor   OBJECT IDENTIFIER ::= { zxAnCesPm 1}
    zxAnCesPmHistory   OBJECT IDENTIFIER ::= { zxAnCesPm 2}

--zxAnCesPmInfor

    zxAnCesWanPortStatisticTable OBJECT-TYPE
        SYNTAX      SEQUENCE OF ZxAnCesWanPortStatisticEntry
        MAX-ACCESS  not-accessible
        STATUS      current
        DESCRIPTION
            "" 
        REFERENCE
            ""
        ::= { zxAnCesPmInfor 1 }

    zxAnCesWanPortStatisticEntry OBJECT-TYPE
        SYNTAX      ZxAnCesWanPortStatisticEntry
        MAX-ACCESS  not-accessible
        STATUS      current
        DESCRIPTION
            ""
        INDEX   { zxPwIndex }
        ::= { zxAnCesWanPortStatisticTable 1 }

    ZxAnCesWanPortStatisticEntry ::=
        SEQUENCE {
            zxAnCesWanPortStatisticEarlyPkts     Unsigned32,
            zxAnCesWanPortStatisticLatePkts     Unsigned32,
            zxAnCesWanPortStatisticUnderrunPkts     Unsigned32,
            zxAnCesWanPortStatisticLostPkts     Unsigned32,
            zxAnCesWanPortStatisticCurQueLen     Unsigned32,
            zxAnCesWanPortStatisticAvgQueLen     Unsigned32,
            zxAnCesWanPortStatisticMaxQueLen     Unsigned32,
            zxAnCesWanPortStatisticMinQueLen     Unsigned32,
            zxAnCesWanPortStatisticPktRxCnt     Unsigned32,
            zxAnCesWanPortStatisticPktTxCnt     Unsigned32,
            zxAnCesWanPortStatisticByteTxCnt     Unsigned32,
            zxAnCesWanPortStatisticLBitCnt     Unsigned32,
            zxAnCesWanPortStatisticLBitSetTime     Unsigned32,
            zxAnCesWanPortStatisticRBitCnt     Unsigned32,
            zxAnCesWanPortStatisticRBitSetTime     Unsigned32
        }

   zxAnCesWanPortStatisticEarlyPkts OBJECT-TYPE
        SYNTAX      Unsigned32
        MAX-ACCESS  read-only
        STATUS      current
        DESCRIPTION
            ""
        ::= { zxAnCesWanPortStatisticEntry 1}

   zxAnCesWanPortStatisticLatePkts OBJECT-TYPE
        SYNTAX      Unsigned32
        MAX-ACCESS  read-only
        STATUS      current
        DESCRIPTION
            ""
        ::= { zxAnCesWanPortStatisticEntry 2}

   zxAnCesWanPortStatisticUnderrunPkts OBJECT-TYPE
        SYNTAX      Unsigned32
        MAX-ACCESS  read-only
        STATUS      current
        DESCRIPTION
            ""
        ::= { zxAnCesWanPortStatisticEntry 3}

   zxAnCesWanPortStatisticLostPkts OBJECT-TYPE
        SYNTAX      Unsigned32
        MAX-ACCESS  read-only
        STATUS      current
        DESCRIPTION
            ""
        ::= { zxAnCesWanPortStatisticEntry 4}

   zxAnCesWanPortStatisticCurQueLen OBJECT-TYPE
        SYNTAX      Unsigned32
        MAX-ACCESS  read-only
        STATUS      current
        DESCRIPTION
            ""
        ::= { zxAnCesWanPortStatisticEntry 5}

   zxAnCesWanPortStatisticAvgQueLen OBJECT-TYPE
        SYNTAX      Unsigned32
        MAX-ACCESS  read-only
        STATUS      current
        DESCRIPTION
            ""
        ::= { zxAnCesWanPortStatisticEntry 6}

   zxAnCesWanPortStatisticMaxQueLen OBJECT-TYPE
        SYNTAX      Unsigned32
        MAX-ACCESS  read-only
        STATUS      current
        DESCRIPTION
            ""
        ::= { zxAnCesWanPortStatisticEntry 7}

   zxAnCesWanPortStatisticMinQueLen OBJECT-TYPE
        SYNTAX      Unsigned32
        MAX-ACCESS  read-only
        STATUS      current
        DESCRIPTION
            ""
        ::= { zxAnCesWanPortStatisticEntry 8}

   zxAnCesWanPortStatisticPktRxCnt OBJECT-TYPE
        SYNTAX      Unsigned32
        MAX-ACCESS  read-only
        STATUS      current
        DESCRIPTION
            ""
        ::= { zxAnCesWanPortStatisticEntry 9}

   zxAnCesWanPortStatisticPktTxCnt OBJECT-TYPE
        SYNTAX      Unsigned32
        MAX-ACCESS  read-only
        STATUS      current
        DESCRIPTION
            ""
        ::= { zxAnCesWanPortStatisticEntry 10}

   zxAnCesWanPortStatisticByteTxCnt OBJECT-TYPE
        SYNTAX      Unsigned32
        MAX-ACCESS  read-only
        STATUS      current
        DESCRIPTION
            ""
        ::= { zxAnCesWanPortStatisticEntry 11}

   zxAnCesWanPortStatisticLBitCnt OBJECT-TYPE
        SYNTAX      Unsigned32
        MAX-ACCESS  read-only
        STATUS      current
        DESCRIPTION
            ""
        ::= { zxAnCesWanPortStatisticEntry 12}

   zxAnCesWanPortStatisticLBitSetTime OBJECT-TYPE
        SYNTAX      Unsigned32
        MAX-ACCESS  read-only
        STATUS      current
        DESCRIPTION
            ""
        ::= { zxAnCesWanPortStatisticEntry 13}

   zxAnCesWanPortStatisticRBitCnt OBJECT-TYPE
        SYNTAX      Unsigned32
        MAX-ACCESS  read-only
        STATUS      current
        DESCRIPTION
            ""
        ::= { zxAnCesWanPortStatisticEntry 14}

   zxAnCesWanPortStatisticRBitSetTime OBJECT-TYPE
        SYNTAX      Unsigned32
        MAX-ACCESS  read-only
        STATUS      current
        DESCRIPTION
            ""
        ::= { zxAnCesWanPortStatisticEntry 15}

    zxAnCesProtocolStatisticTable OBJECT-TYPE
        SYNTAX      SEQUENCE OF ZxAnCesProtocolStatisticEntry
        MAX-ACCESS  not-accessible
        STATUS      current
        DESCRIPTION
            "" 
        REFERENCE
            ""
        ::= { zxAnCesPmInfor 2 }

    zxAnCesProtocolStatisticEntry OBJECT-TYPE
        SYNTAX      ZxAnCesProtocolStatisticEntry
        MAX-ACCESS  not-accessible
        STATUS      current
        DESCRIPTION
            ""
        INDEX   { zxCesCardIndex }
        ::= { zxAnCesProtocolStatisticTable 1 }

    ZxAnCesProtocolStatisticEntry ::=
        SEQUENCE {
            zxAnCesProtocolStatisticProtMatchCnt     Unsigned32,
            zxAnCesProtocolStatisticProtNoMatchCnt     Unsigned32,
            zxAnCesProtocolStatisticClaNoMatchCnt     Unsigned32,
            zxAnCesProtocolStatisticVerifyFailCnt     Unsigned32,
            zxAnCesProtocolStatisticIP4CheckFailCnt     Unsigned32
        }

   zxAnCesProtocolStatisticProtMatchCnt OBJECT-TYPE
        SYNTAX      Unsigned32
        MAX-ACCESS  read-only
        STATUS      current
        DESCRIPTION
            ""
        ::= { zxAnCesProtocolStatisticEntry 1}

   zxAnCesProtocolStatisticProtNoMatchCnt OBJECT-TYPE
        SYNTAX      Unsigned32
        MAX-ACCESS  read-only
        STATUS      current
        DESCRIPTION
            ""
        ::= { zxAnCesProtocolStatisticEntry 2}

   zxAnCesProtocolStatisticClaNoMatchCnt OBJECT-TYPE
        SYNTAX      Unsigned32
        MAX-ACCESS  read-only
        STATUS      current
        DESCRIPTION
            ""
        ::= { zxAnCesProtocolStatisticEntry 3}

   zxAnCesProtocolStatisticVerifyFailCnt OBJECT-TYPE
        SYNTAX      Unsigned32
        MAX-ACCESS  read-only
        STATUS      current
        DESCRIPTION
            ""
        ::= { zxAnCesProtocolStatisticEntry 4}

   zxAnCesProtocolStatisticIP4CheckFailCnt OBJECT-TYPE
        SYNTAX      Unsigned32
        MAX-ACCESS  read-only
        STATUS      current
        DESCRIPTION
            ""
        ::= { zxAnCesProtocolStatisticEntry 5}

    zxAnCesRfc1213StatisticTable OBJECT-TYPE
        SYNTAX      SEQUENCE OF ZxAnCesRfc1213StatisticEntry
        MAX-ACCESS  not-accessible
        STATUS      current
        DESCRIPTION
            "" 
        REFERENCE
            ""
        ::= { zxAnCesPmInfor 3 }

    zxAnCesRfc1213StatisticEntry OBJECT-TYPE
        SYNTAX      ZxAnCesRfc1213StatisticEntry
        MAX-ACCESS  not-accessible
        STATUS      current
        DESCRIPTION
            ""
        INDEX   { zxCesCardIndex }
        ::= { zxAnCesRfc1213StatisticTable 1 }

    ZxAnCesRfc1213StatisticEntry ::=
        SEQUENCE {
            zxAnCesRfc1213StatisticRxOctets     Unsigned32,
            zxAnCesRfc1213StatisticRxUnicastPkts     Unsigned32,
            zxAnCesRfc1213StatisticRxMulBrdPkts     Unsigned32,
            zxAnCesRfc1213StatisticRxDiscardPkts     Unsigned32,
            zxAnCesRfc1213StatisticRxErrorPkts     Unsigned32,
            zxAnCesRfc1213StatisticRxUnknowProtPkts     Unsigned32,
            zxAnCesRfc1213StatisticTxOctets     Unsigned32,
            zxAnCesRfc1213StatisticTxUnicastPkts     Unsigned32,
            zxAnCesRfc1213StatisticTxMulBrdPkts     Unsigned32,
            zxAnCesRfc1213StatisticTxDiscardPkts     Unsigned32,
            zxAnCesRfc1213StatisticTxErrorPkts     Unsigned32,
            zxAnCesRfc1213StatisticOutBoundQueLen     Unsigned32
        }

   zxAnCesRfc1213StatisticRxOctets OBJECT-TYPE
        SYNTAX      Unsigned32
        MAX-ACCESS  read-only
        STATUS      current
        DESCRIPTION
            ""
        ::= { zxAnCesRfc1213StatisticEntry 1}

   zxAnCesRfc1213StatisticRxUnicastPkts OBJECT-TYPE
        SYNTAX      Unsigned32
        MAX-ACCESS  read-only
        STATUS      current
        DESCRIPTION
            ""
        ::= { zxAnCesRfc1213StatisticEntry 2}

   zxAnCesRfc1213StatisticRxMulBrdPkts OBJECT-TYPE
        SYNTAX      Unsigned32
        MAX-ACCESS  read-only
        STATUS      current
        DESCRIPTION
            ""
        ::= { zxAnCesRfc1213StatisticEntry 3}

   zxAnCesRfc1213StatisticRxDiscardPkts OBJECT-TYPE
        SYNTAX      Unsigned32
        MAX-ACCESS  read-only
        STATUS      current
        DESCRIPTION
            ""
        ::= { zxAnCesRfc1213StatisticEntry 4}

   zxAnCesRfc1213StatisticRxErrorPkts OBJECT-TYPE
        SYNTAX      Unsigned32
        MAX-ACCESS  read-only
        STATUS      current
        DESCRIPTION
            ""
        ::= { zxAnCesRfc1213StatisticEntry 5}

   zxAnCesRfc1213StatisticRxUnknowProtPkts OBJECT-TYPE
        SYNTAX      Unsigned32
        MAX-ACCESS  read-only
        STATUS      current
        DESCRIPTION
            ""
        ::= { zxAnCesRfc1213StatisticEntry 6}

   zxAnCesRfc1213StatisticTxOctets OBJECT-TYPE
        SYNTAX      Unsigned32
        MAX-ACCESS  read-only
        STATUS      current
        DESCRIPTION
            ""
        ::= { zxAnCesRfc1213StatisticEntry 7}

   zxAnCesRfc1213StatisticTxUnicastPkts OBJECT-TYPE
        SYNTAX      Unsigned32
        MAX-ACCESS  read-only
        STATUS      current
        DESCRIPTION
            ""
        ::= { zxAnCesRfc1213StatisticEntry 8}

   zxAnCesRfc1213StatisticTxMulBrdPkts OBJECT-TYPE
        SYNTAX      Unsigned32
        MAX-ACCESS  read-only
        STATUS      current
        DESCRIPTION
            ""
        ::= { zxAnCesRfc1213StatisticEntry 9}

   zxAnCesRfc1213StatisticTxDiscardPkts OBJECT-TYPE
        SYNTAX      Unsigned32
        MAX-ACCESS  read-only
        STATUS      current
        DESCRIPTION
            ""
        ::= { zxAnCesRfc1213StatisticEntry 10}

   zxAnCesRfc1213StatisticTxErrorPkts OBJECT-TYPE
        SYNTAX      Unsigned32
        MAX-ACCESS  read-only
        STATUS      current
        DESCRIPTION
            ""
        ::= { zxAnCesRfc1213StatisticEntry 11}

   zxAnCesRfc1213StatisticOutBoundQueLen OBJECT-TYPE
        SYNTAX      Unsigned32
        MAX-ACCESS  read-only
        STATUS      current
        DESCRIPTION
            ""
        ::= { zxAnCesRfc1213StatisticEntry 12}

    zxAnCesRfc1757StatisticTable OBJECT-TYPE
        SYNTAX      SEQUENCE OF ZxAnCesRfc1757StatisticEntry
        MAX-ACCESS  not-accessible
        STATUS      current
        DESCRIPTION
            "" 
        REFERENCE
            ""
        ::= { zxAnCesPmInfor 4 }

    zxAnCesRfc1757StatisticEntry OBJECT-TYPE
        SYNTAX      ZxAnCesRfc1757StatisticEntry
        MAX-ACCESS  not-accessible
        STATUS      current
        DESCRIPTION
            ""
        INDEX   { zxCesCardIndex }
        ::= { zxAnCesRfc1757StatisticTable 1 }

    ZxAnCesRfc1757StatisticEntry ::=
        SEQUENCE {
            zxAnCesRfc1757StatisticDropCnt      Unsigned32,
            zxAnCesRfc1757StatisticMulticastPkts      Unsigned32,
            zxAnCesRfc1757StatisticBroadcastPkts      Unsigned32,
            zxAnCesRfc1757StatisticUndersizeFrmCnt      Unsigned32,
            zxAnCesRfc1757StatisticFragmentsCnt      Unsigned32,
            zxAnCesRfc1757StatisticPkts64      Unsigned32,
            zxAnCesRfc1757StatisticPkts65to127      Unsigned32,
            zxAnCesRfc1757StatisticPkts128to255      Unsigned32,
            zxAnCesRfc1757StatisticPkts256to511      Unsigned32,
            zxAnCesRfc1757StatisticPkts512to1023      Unsigned32,
            zxAnCesRfc1757StatisticPkts1024to1518      Unsigned32,
            zxAnCesRfc1757StatisticPktsOversize      Unsigned32,
            zxAnCesRfc1757StatisticJabberFrmCnt      Unsigned32,
            zxAnCesRfc1757StatisticBytesRx      Unsigned32,
            zxAnCesRfc1757StatisticFramesRx      Unsigned32,
            zxAnCesRfc1757StatisticCollosions       Unsigned32,
            zxAnCesRfc1757StatisticCrcAlignErr       Unsigned32
        }

   zxAnCesRfc1757StatisticDropCnt OBJECT-TYPE
        SYNTAX      Unsigned32
        MAX-ACCESS  read-only
        STATUS      current
        DESCRIPTION
            ""
        ::= { zxAnCesRfc1757StatisticEntry 1}

   zxAnCesRfc1757StatisticMulticastPkts OBJECT-TYPE
        SYNTAX      Unsigned32
        MAX-ACCESS  read-only
        STATUS      current
        DESCRIPTION
            ""
        ::= { zxAnCesRfc1757StatisticEntry 2}

   zxAnCesRfc1757StatisticBroadcastPkts OBJECT-TYPE
        SYNTAX      Unsigned32
        MAX-ACCESS  read-only
        STATUS      current
        DESCRIPTION
            ""
        ::= { zxAnCesRfc1757StatisticEntry 3}

   zxAnCesRfc1757StatisticUndersizeFrmCnt OBJECT-TYPE
        SYNTAX      Unsigned32
        MAX-ACCESS  read-only
        STATUS      current
        DESCRIPTION
            ""
        ::= { zxAnCesRfc1757StatisticEntry 4}

   zxAnCesRfc1757StatisticFragmentsCnt OBJECT-TYPE
        SYNTAX      Unsigned32
        MAX-ACCESS  read-only
        STATUS      current
        DESCRIPTION
            ""
        ::= { zxAnCesRfc1757StatisticEntry 5}

   zxAnCesRfc1757StatisticPkts64 OBJECT-TYPE
        SYNTAX      Unsigned32
        MAX-ACCESS  read-only
        STATUS      current
        DESCRIPTION
            ""
        ::= { zxAnCesRfc1757StatisticEntry 6}

   zxAnCesRfc1757StatisticPkts65to127 OBJECT-TYPE
        SYNTAX      Unsigned32
        MAX-ACCESS  read-only
        STATUS      current
        DESCRIPTION
            ""
        ::= { zxAnCesRfc1757StatisticEntry 7}

   zxAnCesRfc1757StatisticPkts128to255 OBJECT-TYPE
        SYNTAX      Unsigned32
        MAX-ACCESS  read-only
        STATUS      current
        DESCRIPTION
            ""
        ::= { zxAnCesRfc1757StatisticEntry 8}

   zxAnCesRfc1757StatisticPkts256to511 OBJECT-TYPE
        SYNTAX      Unsigned32
        MAX-ACCESS  read-only
        STATUS      current
        DESCRIPTION
            ""
        ::= { zxAnCesRfc1757StatisticEntry 9}

   zxAnCesRfc1757StatisticPkts512to1023 OBJECT-TYPE
        SYNTAX      Unsigned32
        MAX-ACCESS  read-only
        STATUS      current
        DESCRIPTION
            ""
        ::= { zxAnCesRfc1757StatisticEntry 10}

   zxAnCesRfc1757StatisticPkts1024to1518 OBJECT-TYPE
        SYNTAX      Unsigned32
        MAX-ACCESS  read-only
        STATUS      current
        DESCRIPTION
            ""
        ::= { zxAnCesRfc1757StatisticEntry 11}

   zxAnCesRfc1757StatisticPktsOversize OBJECT-TYPE
        SYNTAX      Unsigned32
        MAX-ACCESS  read-only
        STATUS      current
        DESCRIPTION
            ""
        ::= { zxAnCesRfc1757StatisticEntry 12}

   zxAnCesRfc1757StatisticJabberFrmCnt OBJECT-TYPE
        SYNTAX      Unsigned32
        MAX-ACCESS  read-only
        STATUS      current
        DESCRIPTION
            ""
        ::= { zxAnCesRfc1757StatisticEntry 13}

   zxAnCesRfc1757StatisticBytesRx OBJECT-TYPE
        SYNTAX      Unsigned32
        MAX-ACCESS  read-only
        STATUS      current
        DESCRIPTION
            ""
        ::= { zxAnCesRfc1757StatisticEntry 14}

   zxAnCesRfc1757StatisticFramesRx OBJECT-TYPE
        SYNTAX      Unsigned32
        MAX-ACCESS  read-only
        STATUS      current
        DESCRIPTION
            ""
        ::= { zxAnCesRfc1757StatisticEntry 15}

   zxAnCesRfc1757StatisticCollosions OBJECT-TYPE
        SYNTAX      Unsigned32
        MAX-ACCESS  read-only
        STATUS      current
        DESCRIPTION
            ""
        ::= { zxAnCesRfc1757StatisticEntry 16}

   zxAnCesRfc1757StatisticCrcAlignErr OBJECT-TYPE
        SYNTAX      Unsigned32
        MAX-ACCESS  read-only
        STATUS      current
        DESCRIPTION
            ""
        ::= { zxAnCesRfc1757StatisticEntry 17}

 zxAnCesSdhRsB1StatisticTable OBJECT-TYPE
     SYNTAX      SEQUENCE OF ZxAnCesSdhRsB1StatisticEntry
     MAX-ACCESS  not-accessible
     STATUS      current
     DESCRIPTION
         "" 
     REFERENCE
         ""
     ::= { zxAnCesPmInfor 5 }

 zxAnCesSdhRsB1StatisticEntry OBJECT-TYPE
     SYNTAX      ZxAnCesSdhRsB1StatisticEntry
     MAX-ACCESS  not-accessible
     STATUS      current
     DESCRIPTION
         ""
     INDEX   { zxSonetIfIndex }
     ::= { zxAnCesSdhRsB1StatisticTable 1 }

 ZxAnCesSdhRsB1StatisticEntry ::=
     SEQUENCE {
         zxAnCesSdhRsB1Statistic    Unsigned32,
         zxAnCesSdhRsB1BBEStat      Unsigned32,
         zxAnCesSdhRsB1ESStat       Unsigned32,
         zxAnCesSdhRsB1SESStat      Unsigned32,
         zxAnCesSdhRsB1UASStat      Unsigned32
     }

zxAnCesSdhRsB1Statistic OBJECT-TYPE
     SYNTAX      Unsigned32
     MAX-ACCESS  read-only
     STATUS      current
     DESCRIPTION
         ""
     ::= { zxAnCesSdhRsB1StatisticEntry 1}

zxAnCesSdhRsB1BBEStat OBJECT-TYPE
     SYNTAX      Unsigned32
     MAX-ACCESS  read-only
     STATUS      current
     DESCRIPTION
         ""
     ::= { zxAnCesSdhRsB1StatisticEntry 2}
     
zxAnCesSdhRsB1ESStat OBJECT-TYPE
     SYNTAX      Unsigned32
     MAX-ACCESS  read-only
     STATUS      current
     DESCRIPTION
         ""
     ::= { zxAnCesSdhRsB1StatisticEntry 3}
     
zxAnCesSdhRsB1SESStat OBJECT-TYPE
     SYNTAX      Unsigned32
     MAX-ACCESS  read-only
     STATUS      current
     DESCRIPTION
         ""
     ::= { zxAnCesSdhRsB1StatisticEntry 4}
     
zxAnCesSdhRsB1UASStat OBJECT-TYPE
     SYNTAX      Unsigned32
     MAX-ACCESS  read-only
     STATUS      current
     DESCRIPTION
         ""
     ::= { zxAnCesSdhRsB1StatisticEntry 5}
     
 zxAnCesSdhMsB2StatisticTable OBJECT-TYPE
     SYNTAX      SEQUENCE OF ZxAnCesSdhMsB2StatisticEntry
     MAX-ACCESS  not-accessible
     STATUS      current
     DESCRIPTION
         "" 
     REFERENCE
         ""
     ::= { zxAnCesPmInfor 6 }

 zxAnCesSdhMsB2StatisticEntry OBJECT-TYPE
     SYNTAX      ZxAnCesSdhMsB2StatisticEntry
     MAX-ACCESS  not-accessible
     STATUS      current
     DESCRIPTION
         ""
     INDEX   { zxSonetIfIndex }
     ::= { zxAnCesSdhMsB2StatisticTable 1 }

 ZxAnCesSdhMsB2StatisticEntry ::=
     SEQUENCE {
          zxAnCesSdhMsB2Statistic    Unsigned32,
          zxAnCesSdhMsB2BBEStat      Unsigned32,
          zxAnCesSdhMsB2ESStat       Unsigned32,
          zxAnCesSdhMsB2SESStat      Unsigned32,
          zxAnCesSdhMsB2UASStat      Unsigned32
     }

zxAnCesSdhMsB2Statistic OBJECT-TYPE
     SYNTAX      Unsigned32
     MAX-ACCESS  read-only
     STATUS      current
     DESCRIPTION
         ""
     ::= { zxAnCesSdhMsB2StatisticEntry 1}

zxAnCesSdhMsB2BBEStat OBJECT-TYPE
     SYNTAX      Unsigned32
     MAX-ACCESS  read-only
     STATUS      current
     DESCRIPTION
         ""
     ::= { zxAnCesSdhMsB2StatisticEntry 2}
     
zxAnCesSdhMsB2ESStat OBJECT-TYPE
     SYNTAX      Unsigned32
     MAX-ACCESS  read-only
     STATUS      current
     DESCRIPTION
         ""
     ::= { zxAnCesSdhMsB2StatisticEntry 3}
     
zxAnCesSdhMsB2SESStat OBJECT-TYPE
     SYNTAX      Unsigned32
     MAX-ACCESS  read-only
     STATUS      current
     DESCRIPTION
         ""
     ::= { zxAnCesSdhMsB2StatisticEntry 4}
     
zxAnCesSdhMsB2UASStat OBJECT-TYPE
     SYNTAX      Unsigned32
     MAX-ACCESS  read-only
     STATUS      current
     DESCRIPTION
         ""
     ::= { zxAnCesSdhMsB2StatisticEntry 5}
     
 zxAnCesSdhMsB2ReiStatisticTable OBJECT-TYPE
     SYNTAX      SEQUENCE OF ZxAnCesSdhMsB2ReiStatisticEntry
     MAX-ACCESS  not-accessible
     STATUS      current
     DESCRIPTION
         "" 
     REFERENCE
         ""
     ::= { zxAnCesPmInfor 7 }

 zxAnCesSdhMsB2ReiStatisticEntry OBJECT-TYPE
     SYNTAX      ZxAnCesSdhMsB2ReiStatisticEntry
     MAX-ACCESS  not-accessible
     STATUS      current
     DESCRIPTION
         ""
     INDEX   { zxSonetIfIndex }
     ::= { zxAnCesSdhMsB2ReiStatisticTable 1 }

 ZxAnCesSdhMsB2ReiStatisticEntry ::=
     SEQUENCE {
          zxAnCesSdhMsB2ReiStatistic    Unsigned32,
          zxAnCesSdhMsB2ReiBBEStat      Unsigned32,
          zxAnCesSdhMsB2ReiESStat       Unsigned32,
          zxAnCesSdhMsB2ReiSESStat      Unsigned32,
          zxAnCesSdhMsB2ReiUASStat      Unsigned32
     }

zxAnCesSdhMsB2ReiStatistic OBJECT-TYPE
     SYNTAX      Unsigned32
     MAX-ACCESS  read-only
     STATUS      current
     DESCRIPTION
         ""
     ::= { zxAnCesSdhMsB2ReiStatisticEntry 1}

zxAnCesSdhMsB2ReiBBEStat OBJECT-TYPE
     SYNTAX      Unsigned32
     MAX-ACCESS  read-only
     STATUS      current
     DESCRIPTION
         ""
     ::= { zxAnCesSdhMsB2ReiStatisticEntry 2}
     
zxAnCesSdhMsB2ReiESStat OBJECT-TYPE
     SYNTAX      Unsigned32
     MAX-ACCESS  read-only
     STATUS      current
     DESCRIPTION
         ""
     ::= { zxAnCesSdhMsB2ReiStatisticEntry 3}
     
zxAnCesSdhMsB2ReiSESStat OBJECT-TYPE
     SYNTAX      Unsigned32
     MAX-ACCESS  read-only
     STATUS      current
     DESCRIPTION
         ""
     ::= { zxAnCesSdhMsB2ReiStatisticEntry 4}
     
zxAnCesSdhMsB2ReiUASStat OBJECT-TYPE
     SYNTAX      Unsigned32
     MAX-ACCESS  read-only
     STATUS      current
     DESCRIPTION
         ""
     ::= { zxAnCesSdhMsB2ReiStatisticEntry 5}

 zxAnCesSdhVc12V5StatisticTable OBJECT-TYPE
     SYNTAX      SEQUENCE OF ZxAnCesSdhVc12V5StatisticEntry
     MAX-ACCESS  not-accessible
     STATUS      current
     DESCRIPTION
         "" 
     REFERENCE
         ""
     ::= { zxAnCesPmInfor 8 }

 zxAnCesSdhVc12V5StatisticEntry OBJECT-TYPE
     SYNTAX      ZxAnCesSdhVc12V5StatisticEntry
     MAX-ACCESS  not-accessible
     STATUS      current
     DESCRIPTION
         ""
     INDEX   { zxSonetVTIfIndex }
     ::= { zxAnCesSdhVc12V5StatisticTable 1 }

 ZxAnCesSdhVc12V5StatisticEntry ::=
     SEQUENCE {
          zxAnCesSdhVc12V5Statistic    Unsigned32,
          zxAnCesSdhVc12V5BBEStat      Unsigned32,
          zxAnCesSdhVc12V5ESStat       Unsigned32,
          zxAnCesSdhVc12V5SESStat      Unsigned32,
          zxAnCesSdhVc12V5UASStat      Unsigned32
     }

zxAnCesSdhVc12V5Statistic OBJECT-TYPE
     SYNTAX      Unsigned32
     MAX-ACCESS  read-only
     STATUS      current
     DESCRIPTION
         ""
     ::= { zxAnCesSdhVc12V5StatisticEntry 1}
     
 zxAnCesSdhVc12V5BBEStat OBJECT-TYPE
     SYNTAX      Unsigned32
     MAX-ACCESS  read-only
     STATUS      current
     DESCRIPTION
         ""
     ::= { zxAnCesSdhVc12V5StatisticEntry 2}
     
zxAnCesSdhVc12V5ESStat OBJECT-TYPE
     SYNTAX      Unsigned32
     MAX-ACCESS  read-only
     STATUS      current
     DESCRIPTION
         ""
     ::= { zxAnCesSdhVc12V5StatisticEntry 3}
     
zxAnCesSdhVc12V5SESStat OBJECT-TYPE
     SYNTAX      Unsigned32
     MAX-ACCESS  read-only
     STATUS      current
     DESCRIPTION
         ""
     ::= { zxAnCesSdhVc12V5StatisticEntry 4}
     
zxAnCesSdhVc12V5UASStat OBJECT-TYPE
     SYNTAX      Unsigned32
     MAX-ACCESS  read-only
     STATUS      current
     DESCRIPTION
         ""
     ::= { zxAnCesSdhVc12V5StatisticEntry 5}
 
  zxAnCesSdhVc12V5ReiStatisticTable OBJECT-TYPE
     SYNTAX      SEQUENCE OF ZxAnCesSdhVc12V5ReiStatisticEntry
     MAX-ACCESS  not-accessible
     STATUS      current
     DESCRIPTION
         "" 
     REFERENCE
         ""
     ::= { zxAnCesPmInfor 9 }

 zxAnCesSdhVc12V5ReiStatisticEntry OBJECT-TYPE
     SYNTAX      ZxAnCesSdhVc12V5ReiStatisticEntry
     MAX-ACCESS  not-accessible
     STATUS      current
     DESCRIPTION
         ""
     INDEX   { zxSonetVTIfIndex }
     ::= { zxAnCesSdhVc12V5ReiStatisticTable 1 }

 ZxAnCesSdhVc12V5ReiStatisticEntry ::=
     SEQUENCE {
          zxAnCesSdhVc12V5ReiStatistic    Unsigned32,
          zxAnCesSdhVc12V5ReiBBEStat      Unsigned32,
          zxAnCesSdhVc12V5ReiESStat       Unsigned32,
          zxAnCesSdhVc12V5ReiSESStat      Unsigned32,
          zxAnCesSdhVc12V5ReiUASStat      Unsigned32
     }

zxAnCesSdhVc12V5ReiStatistic OBJECT-TYPE
     SYNTAX      Unsigned32
     MAX-ACCESS  read-only
     STATUS      current
     DESCRIPTION
         ""
     ::= { zxAnCesSdhVc12V5ReiStatisticEntry 1}
     
 zxAnCesSdhVc12V5ReiBBEStat OBJECT-TYPE
     SYNTAX      Unsigned32
     MAX-ACCESS  read-only
     STATUS      current
     DESCRIPTION
         ""
     ::= { zxAnCesSdhVc12V5ReiStatisticEntry 2}
     
zxAnCesSdhVc12V5ReiESStat OBJECT-TYPE
     SYNTAX      Unsigned32
     MAX-ACCESS  read-only
     STATUS      current
     DESCRIPTION
         ""
     ::= { zxAnCesSdhVc12V5ReiStatisticEntry 3}
     
zxAnCesSdhVc12V5ReiSESStat OBJECT-TYPE
     SYNTAX      Unsigned32
     MAX-ACCESS  read-only
     STATUS      current
     DESCRIPTION
         ""
     ::= { zxAnCesSdhVc12V5ReiStatisticEntry 4}
     
zxAnCesSdhVc12V5ReiUASStat OBJECT-TYPE
     SYNTAX      Unsigned32
     MAX-ACCESS  read-only
     STATUS      current
     DESCRIPTION
         ""
     ::= { zxAnCesSdhVc12V5ReiStatisticEntry 5}
            
 zxAnCesSdhVc4B3StatisticTable OBJECT-TYPE
     SYNTAX      SEQUENCE OF ZxAnCesSdhVc4B3StatisticEntry
     MAX-ACCESS  not-accessible
     STATUS      current
     DESCRIPTION
         "" 
     REFERENCE
         ""
     ::= { zxAnCesPmInfor 10 }

 zxAnCesSdhVc4B3StatisticEntry OBJECT-TYPE
     SYNTAX      ZxAnCesSdhVc4B3StatisticEntry
     MAX-ACCESS  not-accessible
     STATUS      current
     DESCRIPTION
         ""
     INDEX   { zxSonetIfIndex }
     ::= { zxAnCesSdhVc4B3StatisticTable 1 }

 ZxAnCesSdhVc4B3StatisticEntry ::=
     SEQUENCE {
         zxAnCesSdhVc4B3Statistic    Unsigned32,
         zxAnCesSdhVc4B3BBEStat      Unsigned32,
         zxAnCesSdhVc4B3ESStat       Unsigned32,
         zxAnCesSdhVc4B3SESStat      Unsigned32,
         zxAnCesSdhVc4B3UASStat      Unsigned32
     }

zxAnCesSdhVc4B3Statistic OBJECT-TYPE
     SYNTAX      Unsigned32
     MAX-ACCESS  read-only
     STATUS      current
     DESCRIPTION
         ""
     ::= { zxAnCesSdhVc4B3StatisticEntry 1}

zxAnCesSdhVc4B3BBEStat OBJECT-TYPE
     SYNTAX      Unsigned32
     MAX-ACCESS  read-only
     STATUS      current
     DESCRIPTION
         ""
     ::= { zxAnCesSdhVc4B3StatisticEntry 2}
     
zxAnCesSdhVc4B3ESStat OBJECT-TYPE
     SYNTAX      Unsigned32
     MAX-ACCESS  read-only
     STATUS      current
     DESCRIPTION
         ""
     ::= { zxAnCesSdhVc4B3StatisticEntry 3}
     
zxAnCesSdhVc4B3SESStat OBJECT-TYPE
     SYNTAX      Unsigned32
     MAX-ACCESS  read-only
     STATUS      current
     DESCRIPTION
         ""
     ::= { zxAnCesSdhVc4B3StatisticEntry 4}
     
zxAnCesSdhVc4B3UASStat OBJECT-TYPE
     SYNTAX      Unsigned32
     MAX-ACCESS  read-only
     STATUS      current
     DESCRIPTION
         ""
     ::= { zxAnCesSdhVc4B3StatisticEntry 5}

 zxAnCesSdhVc4B3ReiStatisticTable OBJECT-TYPE
     SYNTAX      SEQUENCE OF ZxAnCesSdhVc4B3ReiStatisticEntry
     MAX-ACCESS  not-accessible
     STATUS      current
     DESCRIPTION
         "" 
     REFERENCE
         ""
     ::= { zxAnCesPmInfor 11 }

 zxAnCesSdhVc4B3ReiStatisticEntry OBJECT-TYPE
     SYNTAX      ZxAnCesSdhVc4B3ReiStatisticEntry
     MAX-ACCESS  not-accessible
     STATUS      current
     DESCRIPTION
         ""
     INDEX   { zxSonetIfIndex }
     ::= { zxAnCesSdhVc4B3ReiStatisticTable 1 }

 ZxAnCesSdhVc4B3ReiStatisticEntry ::=
     SEQUENCE {
         zxAnCesSdhVc4B3ReiStatistic    Unsigned32,
         zxAnCesSdhVc4B3ReiBBEStat      Unsigned32,
         zxAnCesSdhVc4B3ReiESStat       Unsigned32,
         zxAnCesSdhVc4B3ReiSESStat      Unsigned32,
         zxAnCesSdhVc4B3ReiUASStat      Unsigned32
     }

zxAnCesSdhVc4B3ReiStatistic OBJECT-TYPE
     SYNTAX      Unsigned32
     MAX-ACCESS  read-only
     STATUS      current
     DESCRIPTION
         ""
     ::= { zxAnCesSdhVc4B3ReiStatisticEntry 1}

zxAnCesSdhVc4B3ReiBBEStat OBJECT-TYPE
     SYNTAX      Unsigned32
     MAX-ACCESS  read-only
     STATUS      current
     DESCRIPTION
         ""
     ::= { zxAnCesSdhVc4B3ReiStatisticEntry 2}
     
zxAnCesSdhVc4B3ReiESStat OBJECT-TYPE
     SYNTAX      Unsigned32
     MAX-ACCESS  read-only
     STATUS      current
     DESCRIPTION
         ""
     ::= { zxAnCesSdhVc4B3ReiStatisticEntry 3}
     
zxAnCesSdhVc4B3ReiSESStat OBJECT-TYPE
     SYNTAX      Unsigned32
     MAX-ACCESS  read-only
     STATUS      current
     DESCRIPTION
         ""
     ::= { zxAnCesSdhVc4B3ReiStatisticEntry 4}
     
zxAnCesSdhVc4B3ReiUASStat OBJECT-TYPE
     SYNTAX      Unsigned32
     MAX-ACCESS  read-only
     STATUS      current
     DESCRIPTION
         ""
     ::= { zxAnCesSdhVc4B3ReiStatisticEntry 5}
          
--zxAnCesPmHistory

    zxAnCesWanPortStatisticHistoryTable OBJECT-TYPE
        SYNTAX      SEQUENCE OF ZxAnCesWanPortStatisticHistoryEntry
        MAX-ACCESS  not-accessible
        STATUS      current
        DESCRIPTION
            "" 
        REFERENCE
            ""
        ::= { zxAnCesPmHistory 1 }

    zxAnCesWanPortStatisticHistoryEntry OBJECT-TYPE
        SYNTAX      ZxAnCesWanPortStatisticHistoryEntry
        MAX-ACCESS  not-accessible
        STATUS      current
        DESCRIPTION
            ""
        INDEX   { zxPwIndex }
        ::= { zxAnCesWanPortStatisticHistoryTable 1 }

    ZxAnCesWanPortStatisticHistoryEntry ::=
        SEQUENCE {
            zxAnCesWanPortStatisticHistoryEarlyPkts     Unsigned32,
            zxAnCesWanPortStatisticHistoryLatePkts     Unsigned32,
            zxAnCesWanPortStatisticHistoryUnderrunPkts     Unsigned32,
            zxAnCesWanPortStatisticHistoryLostPkts     Unsigned32,
            zxAnCesWanPortStatisticHistoryCurQueLen     Unsigned32,
            zxAnCesWanPortStatisticHistoryAvgQueLen     Unsigned32,
            zxAnCesWanPortStatisticHistoryMaxQueLen     Unsigned32,
            zxAnCesWanPortStatisticHistoryMinQueLen     Unsigned32,
            zxAnCesWanPortStatisticHistoryPktRxCnt     Unsigned32,
            zxAnCesWanPortStatisticHistoryPktTxCnt     Unsigned32,
            zxAnCesWanPortStatisticHistoryByteTxCnt     Unsigned32,
            zxAnCesWanPortStatisticHistoryLBitCnt     Unsigned32,
            zxAnCesWanPortStatisticHistoryLBitSetTime     Unsigned32,
            zxAnCesWanPortStatisticHistoryRBitCnt     Unsigned32,
            zxAnCesWanPortStatisticHistoryRBitSetTime     Unsigned32
        }

   zxAnCesWanPortStatisticHistoryEarlyPkts OBJECT-TYPE
        SYNTAX      Unsigned32
        MAX-ACCESS  read-only
        STATUS      current
        DESCRIPTION
            ""
        ::= { zxAnCesWanPortStatisticHistoryEntry 1}

   zxAnCesWanPortStatisticHistoryLatePkts OBJECT-TYPE
        SYNTAX      Unsigned32
        MAX-ACCESS  read-only
        STATUS      current
        DESCRIPTION
            ""
        ::= { zxAnCesWanPortStatisticHistoryEntry 2}

   zxAnCesWanPortStatisticHistoryUnderrunPkts OBJECT-TYPE
        SYNTAX      Unsigned32
        MAX-ACCESS  read-only
        STATUS      current
        DESCRIPTION
            ""
        ::= { zxAnCesWanPortStatisticHistoryEntry 3}

   zxAnCesWanPortStatisticHistoryLostPkts OBJECT-TYPE
        SYNTAX      Unsigned32
        MAX-ACCESS  read-only
        STATUS      current
        DESCRIPTION
            ""
        ::= { zxAnCesWanPortStatisticHistoryEntry 4}

   zxAnCesWanPortStatisticHistoryCurQueLen OBJECT-TYPE
        SYNTAX      Unsigned32
        MAX-ACCESS  read-only
        STATUS      current
        DESCRIPTION
            ""
        ::= { zxAnCesWanPortStatisticHistoryEntry 5}

   zxAnCesWanPortStatisticHistoryAvgQueLen OBJECT-TYPE
        SYNTAX      Unsigned32
        MAX-ACCESS  read-only
        STATUS      current
        DESCRIPTION
            ""
        ::= { zxAnCesWanPortStatisticHistoryEntry 6}

   zxAnCesWanPortStatisticHistoryMaxQueLen OBJECT-TYPE
        SYNTAX      Unsigned32
        MAX-ACCESS  read-only
        STATUS      current
        DESCRIPTION
            ""
        ::= { zxAnCesWanPortStatisticHistoryEntry 7}

   zxAnCesWanPortStatisticHistoryMinQueLen OBJECT-TYPE
        SYNTAX      Unsigned32
        MAX-ACCESS  read-only
        STATUS      current
        DESCRIPTION
            ""
        ::= { zxAnCesWanPortStatisticHistoryEntry 8}

   zxAnCesWanPortStatisticHistoryPktRxCnt OBJECT-TYPE
        SYNTAX      Unsigned32
        MAX-ACCESS  read-only
        STATUS      current
        DESCRIPTION
            ""
        ::= { zxAnCesWanPortStatisticHistoryEntry 9}

   zxAnCesWanPortStatisticHistoryPktTxCnt OBJECT-TYPE
        SYNTAX      Unsigned32
        MAX-ACCESS  read-only
        STATUS      current
        DESCRIPTION
            ""
        ::= { zxAnCesWanPortStatisticHistoryEntry 10}

   zxAnCesWanPortStatisticHistoryByteTxCnt OBJECT-TYPE
        SYNTAX      Unsigned32
        MAX-ACCESS  read-only
        STATUS      current
        DESCRIPTION
            ""
        ::= { zxAnCesWanPortStatisticHistoryEntry 11}

   zxAnCesWanPortStatisticHistoryLBitCnt OBJECT-TYPE
        SYNTAX      Unsigned32
        MAX-ACCESS  read-only
        STATUS      current
        DESCRIPTION
            ""
        ::= { zxAnCesWanPortStatisticHistoryEntry 12}

   zxAnCesWanPortStatisticHistoryLBitSetTime OBJECT-TYPE
        SYNTAX      Unsigned32
        MAX-ACCESS  read-only
        STATUS      current
        DESCRIPTION
            ""
        ::= { zxAnCesWanPortStatisticHistoryEntry 13}

   zxAnCesWanPortStatisticHistoryRBitCnt OBJECT-TYPE
        SYNTAX      Unsigned32
        MAX-ACCESS  read-only
        STATUS      current
        DESCRIPTION
            ""
        ::= { zxAnCesWanPortStatisticHistoryEntry 14}

   zxAnCesWanPortStatisticHistoryRBitSetTime OBJECT-TYPE
        SYNTAX      Unsigned32
        MAX-ACCESS  read-only
        STATUS      current
        DESCRIPTION
            ""
        ::= { zxAnCesWanPortStatisticHistoryEntry 15}

    zxAnCesProtocolStatisticHistoryTable OBJECT-TYPE
        SYNTAX      SEQUENCE OF ZxAnCesProtocolStatisticHistoryEntry
        MAX-ACCESS  not-accessible
        STATUS      current
        DESCRIPTION
            "" 
        REFERENCE
            ""
        ::= { zxAnCesPmHistory 2 }

    zxAnCesProtocolStatisticHistoryEntry OBJECT-TYPE
        SYNTAX      ZxAnCesProtocolStatisticHistoryEntry
        MAX-ACCESS  not-accessible
        STATUS      current
        DESCRIPTION
            ""
        INDEX   { zxCesCardIndex }
        ::= { zxAnCesProtocolStatisticHistoryTable 1 }

    ZxAnCesProtocolStatisticHistoryEntry ::=
        SEQUENCE {
            zxAnCesProtocolStatisticHistoryProtMatchCnt     Unsigned32,
            zxAnCesProtocolStatisticHistoryProtNoMatchCnt     Unsigned32,
            zxAnCesProtocolStatisticHistoryClaNoMatchCnt     Unsigned32,
            zxAnCesProtocolStatisticHistoryVerifyFailCnt     Unsigned32,
            zxAnCesProtocolStatisticHistoryIP4CheckFailCnt     Unsigned32
        }

   zxAnCesProtocolStatisticHistoryProtMatchCnt OBJECT-TYPE
        SYNTAX      Unsigned32
        MAX-ACCESS  read-only
        STATUS      current
        DESCRIPTION
            ""
        ::= { zxAnCesProtocolStatisticHistoryEntry 1}

   zxAnCesProtocolStatisticHistoryProtNoMatchCnt OBJECT-TYPE
        SYNTAX      Unsigned32
        MAX-ACCESS  read-only
        STATUS      current
        DESCRIPTION
            ""
        ::= { zxAnCesProtocolStatisticHistoryEntry 2}

   zxAnCesProtocolStatisticHistoryClaNoMatchCnt OBJECT-TYPE
        SYNTAX      Unsigned32
        MAX-ACCESS  read-only
        STATUS      current
        DESCRIPTION
            ""
        ::= { zxAnCesProtocolStatisticHistoryEntry 3}

   zxAnCesProtocolStatisticHistoryVerifyFailCnt OBJECT-TYPE
        SYNTAX      Unsigned32
        MAX-ACCESS  read-only
        STATUS      current
        DESCRIPTION
            ""
        ::= { zxAnCesProtocolStatisticHistoryEntry 4}

   zxAnCesProtocolStatisticHistoryIP4CheckFailCnt OBJECT-TYPE
        SYNTAX      Unsigned32
        MAX-ACCESS  read-only
        STATUS      current
        DESCRIPTION
            ""
        ::= { zxAnCesProtocolStatisticHistoryEntry 5}

    zxAnCesRfc1213StatisticHistoryTable OBJECT-TYPE
        SYNTAX      SEQUENCE OF ZxAnCesRfc1213StatisticHistoryEntry
        MAX-ACCESS  not-accessible
        STATUS      current
        DESCRIPTION
            "" 
        REFERENCE
            ""
        ::= { zxAnCesPmHistory 3 }

    zxAnCesRfc1213StatisticHistoryEntry OBJECT-TYPE
        SYNTAX      ZxAnCesRfc1213StatisticHistoryEntry
        MAX-ACCESS  not-accessible
        STATUS      current
        DESCRIPTION
            ""
        INDEX   { zxCesCardIndex }
        ::= { zxAnCesRfc1213StatisticHistoryTable 1 }

    ZxAnCesRfc1213StatisticHistoryEntry ::=
        SEQUENCE {
            zxAnCesRfc1213StatisticHistoryRxOctets     Unsigned32,
            zxAnCesRfc1213StatisticHistoryRxUnicastPkts     Unsigned32,
            zxAnCesRfc1213StatisticHistoryRxMulBrdPkts     Unsigned32,
            zxAnCesRfc1213StatisticHistoryRxDiscardPkts     Unsigned32,
            zxAnCesRfc1213StatisticHistoryRxErrorPkts     Unsigned32,
            zxAnCesRfc1213StatisticHistoryRxUnknowProtPkts     Unsigned32,
            zxAnCesRfc1213StatisticHistoryTxOctets     Unsigned32,
            zxAnCesRfc1213StatisticHistoryTxUnicastPkts     Unsigned32,
            zxAnCesRfc1213StatisticHistoryTxMulBrdPkts     Unsigned32,
            zxAnCesRfc1213StatisticHistoryTxDiscardPkts     Unsigned32,
            zxAnCesRfc1213StatisticHistoryTxErrorPkts     Unsigned32,
            zxAnCesRfc1213StatisticHistoryOutBoundQueLen     Unsigned32
        }

   zxAnCesRfc1213StatisticHistoryRxOctets OBJECT-TYPE
        SYNTAX      Unsigned32
        MAX-ACCESS  read-only
        STATUS      current
        DESCRIPTION
            ""
        ::= { zxAnCesRfc1213StatisticHistoryEntry 1}

   zxAnCesRfc1213StatisticHistoryRxUnicastPkts OBJECT-TYPE
        SYNTAX      Unsigned32
        MAX-ACCESS  read-only
        STATUS      current
        DESCRIPTION
            ""
        ::= { zxAnCesRfc1213StatisticHistoryEntry 2}

   zxAnCesRfc1213StatisticHistoryRxMulBrdPkts OBJECT-TYPE
        SYNTAX      Unsigned32
        MAX-ACCESS  read-only
        STATUS      current
        DESCRIPTION
            ""
        ::= { zxAnCesRfc1213StatisticHistoryEntry 3}

   zxAnCesRfc1213StatisticHistoryRxDiscardPkts OBJECT-TYPE
        SYNTAX      Unsigned32
        MAX-ACCESS  read-only
        STATUS      current
        DESCRIPTION
            ""
        ::= { zxAnCesRfc1213StatisticHistoryEntry 4}

   zxAnCesRfc1213StatisticHistoryRxErrorPkts OBJECT-TYPE
        SYNTAX      Unsigned32
        MAX-ACCESS  read-only
        STATUS      current
        DESCRIPTION
            ""
        ::= { zxAnCesRfc1213StatisticHistoryEntry 5}

   zxAnCesRfc1213StatisticHistoryRxUnknowProtPkts OBJECT-TYPE
        SYNTAX      Unsigned32
        MAX-ACCESS  read-only
        STATUS      current
        DESCRIPTION
            ""
        ::= { zxAnCesRfc1213StatisticHistoryEntry 6}

   zxAnCesRfc1213StatisticHistoryTxOctets OBJECT-TYPE
        SYNTAX      Unsigned32
        MAX-ACCESS  read-only
        STATUS      current
        DESCRIPTION
            ""
        ::= { zxAnCesRfc1213StatisticHistoryEntry 7}

   zxAnCesRfc1213StatisticHistoryTxUnicastPkts OBJECT-TYPE
        SYNTAX      Unsigned32
        MAX-ACCESS  read-only
        STATUS      current
        DESCRIPTION
            ""
        ::= { zxAnCesRfc1213StatisticHistoryEntry 8}

   zxAnCesRfc1213StatisticHistoryTxMulBrdPkts OBJECT-TYPE
        SYNTAX      Unsigned32
        MAX-ACCESS  read-only
        STATUS      current
        DESCRIPTION
            ""
        ::= { zxAnCesRfc1213StatisticHistoryEntry 9}

   zxAnCesRfc1213StatisticHistoryTxDiscardPkts OBJECT-TYPE
        SYNTAX      Unsigned32
        MAX-ACCESS  read-only
        STATUS      current
        DESCRIPTION
            ""
        ::= { zxAnCesRfc1213StatisticHistoryEntry 10}

   zxAnCesRfc1213StatisticHistoryTxErrorPkts OBJECT-TYPE
        SYNTAX      Unsigned32
        MAX-ACCESS  read-only
        STATUS      current
        DESCRIPTION
            ""
        ::= { zxAnCesRfc1213StatisticHistoryEntry 11}

   zxAnCesRfc1213StatisticHistoryOutBoundQueLen OBJECT-TYPE
        SYNTAX      Unsigned32
        MAX-ACCESS  read-only
        STATUS      current
        DESCRIPTION
            ""
        ::= { zxAnCesRfc1213StatisticHistoryEntry 12}

    zxAnCesRfc1757StatisticHistoryTable OBJECT-TYPE
        SYNTAX      SEQUENCE OF ZxAnCesRfc1757StatisticHistoryEntry
        MAX-ACCESS  not-accessible
        STATUS      current
        DESCRIPTION
            "" 
        REFERENCE
            ""
        ::= { zxAnCesPmHistory 4 }

    zxAnCesRfc1757StatisticHistoryEntry OBJECT-TYPE
        SYNTAX      ZxAnCesRfc1757StatisticHistoryEntry
        MAX-ACCESS  not-accessible
        STATUS      current
        DESCRIPTION
            ""
        INDEX   { zxCesCardIndex }
        ::= { zxAnCesRfc1757StatisticHistoryTable 1 }

    ZxAnCesRfc1757StatisticHistoryEntry ::=
        SEQUENCE {
            zxAnCesRfc1757StatisticHistoryDropCnt      Unsigned32,
            zxAnCesRfc1757StatisticHistoryMulticastPkts      Unsigned32,
            zxAnCesRfc1757StatisticHistoryBroadcastPkts      Unsigned32,
            zxAnCesRfc1757StatisticHistoryUndersizeFrmCnt      Unsigned32,
            zxAnCesRfc1757StatisticHistoryFragmentsCnt      Unsigned32,
            zxAnCesRfc1757StatisticHistoryPkts64      Unsigned32,
            zxAnCesRfc1757StatisticHistoryPkts65to127      Unsigned32,
            zxAnCesRfc1757StatisticHistoryPkts128to255      Unsigned32,
            zxAnCesRfc1757StatisticHistoryPkts256to511      Unsigned32,
            zxAnCesRfc1757StatisticHistoryPkts512to1023      Unsigned32,
            zxAnCesRfc1757StatisticHistoryPkts1024to1518      Unsigned32,
            zxAnCesRfc1757StatisticHistoryPktsOversize      Unsigned32,
            zxAnCesRfc1757StatisticHistoryJabberFrmCnt      Unsigned32,
            zxAnCesRfc1757StatisticHistoryBytesRx      Unsigned32,
            zxAnCesRfc1757StatisticHistoryFramesRx      Unsigned32,
            zxAnCesRfc1757StatisticHistoryCollosions       Unsigned32,
            zxAnCesRfc1757StatisticHistoryCrcAlignErr       Unsigned32
        }

   zxAnCesRfc1757StatisticHistoryDropCnt OBJECT-TYPE
        SYNTAX      Unsigned32
        MAX-ACCESS  read-only
        STATUS      current
        DESCRIPTION
            ""
        ::= { zxAnCesRfc1757StatisticHistoryEntry 1}

   zxAnCesRfc1757StatisticHistoryMulticastPkts OBJECT-TYPE
        SYNTAX      Unsigned32
        MAX-ACCESS  read-only
        STATUS      current
        DESCRIPTION
            ""
        ::= { zxAnCesRfc1757StatisticHistoryEntry 2}

   zxAnCesRfc1757StatisticHistoryBroadcastPkts OBJECT-TYPE
        SYNTAX      Unsigned32
        MAX-ACCESS  read-only
        STATUS      current
        DESCRIPTION
            ""
        ::= { zxAnCesRfc1757StatisticHistoryEntry 3}

   zxAnCesRfc1757StatisticHistoryUndersizeFrmCnt OBJECT-TYPE
        SYNTAX      Unsigned32
        MAX-ACCESS  read-only
        STATUS      current
        DESCRIPTION
            ""
        ::= { zxAnCesRfc1757StatisticHistoryEntry 4}

   zxAnCesRfc1757StatisticHistoryFragmentsCnt OBJECT-TYPE
        SYNTAX      Unsigned32
        MAX-ACCESS  read-only
        STATUS      current
        DESCRIPTION
            ""
        ::= { zxAnCesRfc1757StatisticHistoryEntry 5}

   zxAnCesRfc1757StatisticHistoryPkts64 OBJECT-TYPE
        SYNTAX      Unsigned32
        MAX-ACCESS  read-only
        STATUS      current
        DESCRIPTION
            ""
        ::= { zxAnCesRfc1757StatisticHistoryEntry 6}

   zxAnCesRfc1757StatisticHistoryPkts65to127 OBJECT-TYPE
        SYNTAX      Unsigned32
        MAX-ACCESS  read-only
        STATUS      current
        DESCRIPTION
            ""
        ::= { zxAnCesRfc1757StatisticHistoryEntry 7}

   zxAnCesRfc1757StatisticHistoryPkts128to255 OBJECT-TYPE
        SYNTAX      Unsigned32
        MAX-ACCESS  read-only
        STATUS      current
        DESCRIPTION
            ""
        ::= { zxAnCesRfc1757StatisticHistoryEntry 8}

   zxAnCesRfc1757StatisticHistoryPkts256to511 OBJECT-TYPE
        SYNTAX      Unsigned32
        MAX-ACCESS  read-only
        STATUS      current
        DESCRIPTION
            ""
        ::= { zxAnCesRfc1757StatisticHistoryEntry 9}

   zxAnCesRfc1757StatisticHistoryPkts512to1023 OBJECT-TYPE
        SYNTAX      Unsigned32
        MAX-ACCESS  read-only
        STATUS      current
        DESCRIPTION
            ""
        ::= { zxAnCesRfc1757StatisticHistoryEntry 10}

   zxAnCesRfc1757StatisticHistoryPkts1024to1518 OBJECT-TYPE
        SYNTAX      Unsigned32
        MAX-ACCESS  read-only
        STATUS      current
        DESCRIPTION
            ""
        ::= { zxAnCesRfc1757StatisticHistoryEntry 11}

   zxAnCesRfc1757StatisticHistoryPktsOversize OBJECT-TYPE
        SYNTAX      Unsigned32
        MAX-ACCESS  read-only
        STATUS      current
        DESCRIPTION
            ""
        ::= { zxAnCesRfc1757StatisticHistoryEntry 12}

   zxAnCesRfc1757StatisticHistoryJabberFrmCnt OBJECT-TYPE
        SYNTAX      Unsigned32
        MAX-ACCESS  read-only
        STATUS      current
        DESCRIPTION
            ""
        ::= { zxAnCesRfc1757StatisticHistoryEntry 13}

   zxAnCesRfc1757StatisticHistoryBytesRx OBJECT-TYPE
        SYNTAX      Unsigned32
        MAX-ACCESS  read-only
        STATUS      current
        DESCRIPTION
            ""
        ::= { zxAnCesRfc1757StatisticHistoryEntry 14}

   zxAnCesRfc1757StatisticHistoryFramesRx OBJECT-TYPE
        SYNTAX      Unsigned32
        MAX-ACCESS  read-only
        STATUS      current
        DESCRIPTION
            ""
        ::= { zxAnCesRfc1757StatisticHistoryEntry 15}

   zxAnCesRfc1757StatisticHistoryCollosions OBJECT-TYPE
        SYNTAX      Unsigned32
        MAX-ACCESS  read-only
        STATUS      current
        DESCRIPTION
            ""
        ::= { zxAnCesRfc1757StatisticHistoryEntry 16}

   zxAnCesRfc1757StatisticHistoryCrcAlignErr OBJECT-TYPE
        SYNTAX      Unsigned32
        MAX-ACCESS  read-only
        STATUS      current
        DESCRIPTION
            ""
        ::= { zxAnCesRfc1757StatisticHistoryEntry 17}

 zxAnCesSdhRsB1StatisticHistoryTable OBJECT-TYPE
     SYNTAX      SEQUENCE OF ZxAnCesSdhRsB1StatisticHistoryEntry
     MAX-ACCESS  not-accessible
     STATUS      current
     DESCRIPTION
         "" 
     REFERENCE
         ""
     ::= { zxAnCesPmHistory 5 }

 zxAnCesSdhRsB1StatisticHistoryEntry OBJECT-TYPE
     SYNTAX      ZxAnCesSdhRsB1StatisticHistoryEntry
     MAX-ACCESS  not-accessible
     STATUS      current
     DESCRIPTION
         ""
     INDEX   { zxSonetIfIndex }
     ::= { zxAnCesSdhRsB1StatisticHistoryTable 1 }

 ZxAnCesSdhRsB1StatisticHistoryEntry ::=
     SEQUENCE {
         zxAnCesSdhRsB1StatisticHistory    Unsigned32,
         zxAnCesSdhRsB1BBEStatHistory      Unsigned32,
         zxAnCesSdhRsB1ESStatHistory       Unsigned32,
         zxAnCesSdhRsB1SESStatHistory      Unsigned32,
         zxAnCesSdhRsB1UASStatHistory      Unsigned32
     }

zxAnCesSdhRsB1StatisticHistory OBJECT-TYPE
     SYNTAX      Unsigned32
     MAX-ACCESS  read-only
     STATUS      current
     DESCRIPTION
         ""
     ::= { zxAnCesSdhRsB1StatisticHistoryEntry 1}

zxAnCesSdhRsB1BBEStatHistory OBJECT-TYPE
     SYNTAX      Unsigned32
     MAX-ACCESS  read-only
     STATUS      current
     DESCRIPTION
         ""
     ::= { zxAnCesSdhRsB1StatisticHistoryEntry 2}
     
zxAnCesSdhRsB1ESStatHistory OBJECT-TYPE
     SYNTAX      Unsigned32
     MAX-ACCESS  read-only
     STATUS      current
     DESCRIPTION
         ""
     ::= { zxAnCesSdhRsB1StatisticHistoryEntry 3}
     
zxAnCesSdhRsB1SESStatHistory OBJECT-TYPE
     SYNTAX      Unsigned32
     MAX-ACCESS  read-only
     STATUS      current
     DESCRIPTION
         ""
     ::= { zxAnCesSdhRsB1StatisticHistoryEntry 4}
     
zxAnCesSdhRsB1UASStatHistory OBJECT-TYPE
     SYNTAX      Unsigned32
     MAX-ACCESS  read-only
     STATUS      current
     DESCRIPTION
         ""
     ::= { zxAnCesSdhRsB1StatisticHistoryEntry 5}
     
 zxAnCesSdhMsB2StatisticHistoryTable OBJECT-TYPE
     SYNTAX      SEQUENCE OF ZxAnCesSdhMsB2StatisticHistoryEntry
     MAX-ACCESS  not-accessible
     STATUS      current
     DESCRIPTION
         "" 
     REFERENCE
         ""
     ::= { zxAnCesPmHistory 6 }

 zxAnCesSdhMsB2StatisticHistoryEntry OBJECT-TYPE
     SYNTAX      ZxAnCesSdhMsB2StatisticHistoryEntry
     MAX-ACCESS  not-accessible
     STATUS      current
     DESCRIPTION
         ""
     INDEX   { zxSonetIfIndex }
     ::= { zxAnCesSdhMsB2StatisticHistoryTable 1 }

 ZxAnCesSdhMsB2StatisticHistoryEntry ::=
     SEQUENCE {
         zxAnCesSdhMsB2StatisticHistory    Unsigned32,
         zxAnCesSdhMsB2BBEStatHistory      Unsigned32,
         zxAnCesSdhMsB2ESStatHistory       Unsigned32,
         zxAnCesSdhMsB2SESStatHistory      Unsigned32,
         zxAnCesSdhMsB2UASStatHistory      Unsigned32
     }

zxAnCesSdhMsB2StatisticHistory OBJECT-TYPE
     SYNTAX      Unsigned32
     MAX-ACCESS  read-only
     STATUS      current
     DESCRIPTION
         ""
     ::= { zxAnCesSdhMsB2StatisticHistoryEntry 1}

zxAnCesSdhMsB2BBEStatHistory OBJECT-TYPE
     SYNTAX      Unsigned32
     MAX-ACCESS  read-only
     STATUS      current
     DESCRIPTION
         ""
     ::= { zxAnCesSdhMsB2StatisticHistoryEntry 2}
     
zxAnCesSdhMsB2ESStatHistory OBJECT-TYPE
     SYNTAX      Unsigned32
     MAX-ACCESS  read-only
     STATUS      current
     DESCRIPTION
         ""
     ::= { zxAnCesSdhMsB2StatisticHistoryEntry 3}
     
zxAnCesSdhMsB2SESStatHistory OBJECT-TYPE
     SYNTAX      Unsigned32
     MAX-ACCESS  read-only
     STATUS      current
     DESCRIPTION
         ""
     ::= { zxAnCesSdhMsB2StatisticHistoryEntry 4}
     
zxAnCesSdhMsB2UASStatHistory OBJECT-TYPE
     SYNTAX      Unsigned32
     MAX-ACCESS  read-only
     STATUS      current
     DESCRIPTION
         ""
     ::= { zxAnCesSdhMsB2StatisticHistoryEntry 5}
     
 zxAnCesSdhMsB2ReiStatisticHistoryTable OBJECT-TYPE
     SYNTAX      SEQUENCE OF ZxAnCesSdhMsB2ReiStatisticHistoryEntry
     MAX-ACCESS  not-accessible
     STATUS      current
     DESCRIPTION
         "" 
     REFERENCE
         ""
     ::= { zxAnCesPmHistory 7 }

 zxAnCesSdhMsB2ReiStatisticHistoryEntry OBJECT-TYPE
     SYNTAX      ZxAnCesSdhMsB2ReiStatisticHistoryEntry
     MAX-ACCESS  not-accessible
     STATUS      current
     DESCRIPTION
         ""
     INDEX   { zxSonetIfIndex }
     ::= { zxAnCesSdhMsB2ReiStatisticHistoryTable 1 }

 ZxAnCesSdhMsB2ReiStatisticHistoryEntry ::=
     SEQUENCE {
         zxAnCesSdhMsB2ReiStatisticHistory    Unsigned32,
         zxAnCesSdhMsB2ReiBBEStatHistory      Unsigned32,
         zxAnCesSdhMsB2ReiESStatHistory       Unsigned32,
         zxAnCesSdhMsB2ReiSESStatHistory      Unsigned32,
         zxAnCesSdhMsB2ReiUASStatHistory      Unsigned32
     }

zxAnCesSdhMsB2ReiStatisticHistory OBJECT-TYPE
     SYNTAX      Unsigned32
     MAX-ACCESS  read-only
     STATUS      current
     DESCRIPTION
         ""
     ::= { zxAnCesSdhMsB2ReiStatisticHistoryEntry 1}
     
zxAnCesSdhMsB2ReiBBEStatHistory OBJECT-TYPE
     SYNTAX      Unsigned32
     MAX-ACCESS  read-only
     STATUS      current
     DESCRIPTION
         ""
     ::= { zxAnCesSdhMsB2ReiStatisticHistoryEntry 2}
     
zxAnCesSdhMsB2ReiESStatHistory OBJECT-TYPE
     SYNTAX      Unsigned32
     MAX-ACCESS  read-only
     STATUS      current
     DESCRIPTION
         ""
     ::= { zxAnCesSdhMsB2ReiStatisticHistoryEntry 3}
     
zxAnCesSdhMsB2ReiSESStatHistory OBJECT-TYPE
     SYNTAX      Unsigned32
     MAX-ACCESS  read-only
     STATUS      current
     DESCRIPTION
         ""
     ::= { zxAnCesSdhMsB2ReiStatisticHistoryEntry 4}
     
zxAnCesSdhMsB2ReiUASStatHistory OBJECT-TYPE
     SYNTAX      Unsigned32
     MAX-ACCESS  read-only
     STATUS      current
     DESCRIPTION
         ""
     ::= { zxAnCesSdhMsB2ReiStatisticHistoryEntry 5}
     
 zxAnCesSdhVc12V5StatisticHistoryTable OBJECT-TYPE
     SYNTAX      SEQUENCE OF ZxAnCesSdhVc12V5StatisticHistoryEntry
     MAX-ACCESS  not-accessible
     STATUS      current
     DESCRIPTION
         "" 
     REFERENCE
         ""
     ::= { zxAnCesPmHistory 8 }

 zxAnCesSdhVc12V5StatisticHistoryEntry OBJECT-TYPE
     SYNTAX      ZxAnCesSdhVc12V5StatisticHistoryEntry
     MAX-ACCESS  not-accessible
     STATUS      current
     DESCRIPTION
         ""
     INDEX   { zxSonetVTIfIndex }
     ::= { zxAnCesSdhVc12V5StatisticHistoryTable 1 }

 ZxAnCesSdhVc12V5StatisticHistoryEntry ::=
     SEQUENCE {
         zxAnCesSdhVc12V5StatisticHistory    Unsigned32,
         zxAnCesSdhVc12V5BBEStatHistory      Unsigned32,
         zxAnCesSdhVc12V5ESStatHistory       Unsigned32,
         zxAnCesSdhVc12V5SESStatHistory      Unsigned32,
         zxAnCesSdhVc12V5UASStatHistory      Unsigned32
     }

zxAnCesSdhVc12V5StatisticHistory OBJECT-TYPE
     SYNTAX      Unsigned32
     MAX-ACCESS  read-only
     STATUS      current
     DESCRIPTION
         ""
     ::= { zxAnCesSdhVc12V5StatisticHistoryEntry 1}
     
zxAnCesSdhVc12V5BBEStatHistory OBJECT-TYPE
     SYNTAX      Unsigned32
     MAX-ACCESS  read-only
     STATUS      current
     DESCRIPTION
         ""
     ::= { zxAnCesSdhVc12V5StatisticHistoryEntry 2}
     
zxAnCesSdhVc12V5ESStatHistory OBJECT-TYPE
     SYNTAX      Unsigned32
     MAX-ACCESS  read-only
     STATUS      current
     DESCRIPTION
         ""
     ::= { zxAnCesSdhVc12V5StatisticHistoryEntry 3}
     
zxAnCesSdhVc12V5SESStatHistory OBJECT-TYPE
     SYNTAX      Unsigned32
     MAX-ACCESS  read-only
     STATUS      current
     DESCRIPTION
         ""
     ::= { zxAnCesSdhVc12V5StatisticHistoryEntry 4}
     
zxAnCesSdhVc12V5UASStatHistory OBJECT-TYPE
     SYNTAX      Unsigned32
     MAX-ACCESS  read-only
     STATUS      current
     DESCRIPTION
         ""
     ::= { zxAnCesSdhVc12V5StatisticHistoryEntry 5}
 
 zxAnCesSdhVc12V5ReiStatHistoryTable OBJECT-TYPE
     SYNTAX      SEQUENCE OF ZxAnCesSdhVc12V5ReiStatHistoryEntry
     MAX-ACCESS  not-accessible
     STATUS      current
     DESCRIPTION
         "" 
     REFERENCE
         ""
     ::= { zxAnCesPmHistory 9 }

 zxAnCesSdhVc12V5ReiStatHistoryEntry OBJECT-TYPE
     SYNTAX      ZxAnCesSdhVc12V5ReiStatHistoryEntry
     MAX-ACCESS  not-accessible
     STATUS      current
     DESCRIPTION
         ""
     INDEX   { zxSonetVTIfIndex }
     ::= { zxAnCesSdhVc12V5ReiStatHistoryTable 1 }

 ZxAnCesSdhVc12V5ReiStatHistoryEntry ::=
     SEQUENCE {
         zxAnCesSdhVc12V5ReiStatHistory    Unsigned32,
         zxAnCesSdhVc12V5ReiBBEStatHistory      Unsigned32,
         zxAnCesSdhVc12V5ReiESStatHistory       Unsigned32,
         zxAnCesSdhVc12V5ReiSESStatHistory      Unsigned32,
         zxAnCesSdhVc12V5ReiUASStatHistory      Unsigned32
     }

zxAnCesSdhVc12V5ReiStatHistory OBJECT-TYPE
     SYNTAX      Unsigned32
     MAX-ACCESS  read-only
     STATUS      current
     DESCRIPTION
         ""
     ::= { zxAnCesSdhVc12V5ReiStatHistoryEntry 1}
     
zxAnCesSdhVc12V5ReiBBEStatHistory OBJECT-TYPE
     SYNTAX      Unsigned32
     MAX-ACCESS  read-only
     STATUS      current
     DESCRIPTION
         ""
     ::= { zxAnCesSdhVc12V5ReiStatHistoryEntry 2}
     
zxAnCesSdhVc12V5ReiESStatHistory OBJECT-TYPE
     SYNTAX      Unsigned32
     MAX-ACCESS  read-only
     STATUS      current
     DESCRIPTION
         ""
     ::= { zxAnCesSdhVc12V5ReiStatHistoryEntry 3}
     
zxAnCesSdhVc12V5ReiSESStatHistory OBJECT-TYPE
     SYNTAX      Unsigned32
     MAX-ACCESS  read-only
     STATUS      current
     DESCRIPTION
         ""
     ::= { zxAnCesSdhVc12V5ReiStatHistoryEntry 4}
     
zxAnCesSdhVc12V5ReiUASStatHistory OBJECT-TYPE
     SYNTAX      Unsigned32
     MAX-ACCESS  read-only
     STATUS      current
     DESCRIPTION
         ""
     ::= { zxAnCesSdhVc12V5ReiStatHistoryEntry 5}
         
 zxAnCesSdhVc4B3StatisticHistoryTable OBJECT-TYPE
     SYNTAX      SEQUENCE OF ZxAnCesSdhVc4B3StatisticHistoryEntry
     MAX-ACCESS  not-accessible
     STATUS      current
     DESCRIPTION
         "" 
     REFERENCE
         ""
     ::= { zxAnCesPmHistory 10 }

 zxAnCesSdhVc4B3StatisticHistoryEntry OBJECT-TYPE
     SYNTAX      ZxAnCesSdhVc4B3StatisticHistoryEntry
     MAX-ACCESS  not-accessible
     STATUS      current
     DESCRIPTION
         ""
     INDEX   { zxSonetIfIndex }
     ::= { zxAnCesSdhVc4B3StatisticHistoryTable 1 }

 ZxAnCesSdhVc4B3StatisticHistoryEntry ::=
     SEQUENCE {
         zxAnCesSdhVc4B3StatisticHistory    Unsigned32,
         zxAnCesSdhVc4B3BBEStatHistory      Unsigned32,
         zxAnCesSdhVc4B3ESStatHistory       Unsigned32,
         zxAnCesSdhVc4B3SESStatHistory      Unsigned32,
         zxAnCesSdhVc4B3UASStatHistory      Unsigned32
     }

zxAnCesSdhVc4B3StatisticHistory OBJECT-TYPE
     SYNTAX      Unsigned32
     MAX-ACCESS  read-only
     STATUS      current
     DESCRIPTION
         ""
     ::= { zxAnCesSdhVc4B3StatisticHistoryEntry 1}

zxAnCesSdhVc4B3BBEStatHistory OBJECT-TYPE
     SYNTAX      Unsigned32
     MAX-ACCESS  read-only
     STATUS      current
     DESCRIPTION
         ""
     ::= { zxAnCesSdhVc4B3StatisticHistoryEntry 2}
     
zxAnCesSdhVc4B3ESStatHistory OBJECT-TYPE
     SYNTAX      Unsigned32
     MAX-ACCESS  read-only
     STATUS      current
     DESCRIPTION
         ""
     ::= { zxAnCesSdhVc4B3StatisticHistoryEntry 3}
     
zxAnCesSdhVc4B3SESStatHistory OBJECT-TYPE
     SYNTAX      Unsigned32
     MAX-ACCESS  read-only
     STATUS      current
     DESCRIPTION
         ""
     ::= { zxAnCesSdhVc4B3StatisticHistoryEntry 4}
     
zxAnCesSdhVc4B3UASStatHistory OBJECT-TYPE
     SYNTAX      Unsigned32
     MAX-ACCESS  read-only
     STATUS      current
     DESCRIPTION
         ""
     ::= { zxAnCesSdhVc4B3StatisticHistoryEntry 5}
     
 zxAnCesSdhVc4B3ReiStatisticHistoryTable OBJECT-TYPE
     SYNTAX      SEQUENCE OF ZxAnCesSdhVc4B3ReiStatisticHistoryEntry
     MAX-ACCESS  not-accessible
     STATUS      current
     DESCRIPTION
         "" 
     REFERENCE
         ""
     ::= { zxAnCesPmHistory 11 }

 zxAnCesSdhVc4B3ReiStatisticHistoryEntry OBJECT-TYPE
     SYNTAX      ZxAnCesSdhVc4B3ReiStatisticHistoryEntry
     MAX-ACCESS  not-accessible
     STATUS      current
     DESCRIPTION
         ""
     INDEX   { zxSonetIfIndex }
     ::= { zxAnCesSdhVc4B3ReiStatisticHistoryTable 1 }

 ZxAnCesSdhVc4B3ReiStatisticHistoryEntry ::=
     SEQUENCE {
         zxAnCesSdhVc4B3ReiStatisticHistory    Unsigned32,
         zxAnCesSdhVc4B3ReiBBEStatHistory      Unsigned32,
         zxAnCesSdhVc4B3ReiESStatHistory       Unsigned32,
         zxAnCesSdhVc4B3ReiSESStatHistory      Unsigned32,
         zxAnCesSdhVc4B3ReiUASStatHistory      Unsigned32
     }

zxAnCesSdhVc4B3ReiStatisticHistory OBJECT-TYPE
     SYNTAX      Unsigned32
     MAX-ACCESS  read-only
     STATUS      current
     DESCRIPTION
         ""
     ::= { zxAnCesSdhVc4B3ReiStatisticHistoryEntry 1}

zxAnCesSdhVc4B3ReiBBEStatHistory OBJECT-TYPE
     SYNTAX      Unsigned32
     MAX-ACCESS  read-only
     STATUS      current
     DESCRIPTION
         ""
     ::= { zxAnCesSdhVc4B3ReiStatisticHistoryEntry 2}
     
zxAnCesSdhVc4B3ReiESStatHistory OBJECT-TYPE
     SYNTAX      Unsigned32
     MAX-ACCESS  read-only
     STATUS      current
     DESCRIPTION
         ""
     ::= { zxAnCesSdhVc4B3ReiStatisticHistoryEntry 3}
     
zxAnCesSdhVc4B3ReiSESStatHistory OBJECT-TYPE
     SYNTAX      Unsigned32
     MAX-ACCESS  read-only
     STATUS      current
     DESCRIPTION
         ""
     ::= { zxAnCesSdhVc4B3ReiStatisticHistoryEntry 4}
     
zxAnCesSdhVc4B3ReiUASStatHistory OBJECT-TYPE
     SYNTAX      Unsigned32
     MAX-ACCESS  read-only
     STATUS      current
     DESCRIPTION
         ""
     ::= { zxAnCesSdhVc4B3ReiStatisticHistoryEntry 5}
END
